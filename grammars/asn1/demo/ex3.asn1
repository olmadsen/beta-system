%%% ex3: ModuleDefinition: asn1 %%%

Parameter-ASN1Module  {joint-iso-ccitt ms(9) smi(3) part2(2) asn1Module(2)  3 }
DEFINITIONS  IMPLICIT TAGS::=
BEGIN
smi2Parameter OBJECT IDENTIFIER  ::=    {  joint-iso-ccitt ms (9)  smi(3)
part2(2)  parameter(5) 3}
MiscellaneousError ::= NULL
END
