%%% ex2: ModuleDefinition: asn1 %%%

Notification-ASN1Module  {joint-iso-ccitt ms(9) smi(3) part2(2) asn1Module(2)  2 }
DEFINITIONS  IMPLICIT TAGS::=
BEGIN
IMPORTS 
ProbableCause,SpecificProblems, PerceivedSeverity, BackedUpStatus,  TrendIndication, ThresholdInfo, NotificationIdentifier, CorrelatedNotifications,  MonitoredAttributes, 
ProposedRepairActions, AdditionalText, AdditionalInformation, SecurityAlarmCause, SecurityAlarmSeverity, SecurityAlarmDetector, AttributeValueChangeDefinition, 
SourceIndicator, AttributeIdentifierList, AttributeList, ServiceUser, ServiceProvider 
FROM	Attribute-ASN1Module
	ObjectClass,AttributeId,ObjectInstance  FROM CMIP-1 {joint-iso-ccitt  ms(9) cmip(1) version1 (1) protocol(3)} ;

smi2Notification OBJECT IDENTIFIER  ::=    {  joint-iso-ccitt ms (9)   smi(3) part2(2)  notification(10)}

Alarminfo ::=  SEQUENCE {
	probableCause		ProbableCause,
	specificProblems 	[1]	SpecificProblems OPTIONAL,
	perceivedSeverity 		PerceivedSeverity,
	backedUpStatus			BackedUpStatus  OPTIONAL,
	backUpObject		[2]	ObjectInstance  OPTIONAL,
	trendIndication		[3]	TrendIndication  OPTIONAL,
	thresholdInfo		[4]	ThresholdInfo   OPTIONAL,
	notificationIdentifier	[5]	NotificationIdentifier  OPTIONAL,
	correlatedNotifications	[6]	CorrelatedNotifications  OPTIONAL,
	stateChangeDefinition	[7]	AttributeValueChangeDefinition	OPTIONAL,
	monitoredAttributes	[8]	MonitoredAttributes  OPTIONAL,
	proposedRepairActions	[9]	ProposedRepairActions	OPTIONAL,
	additionalText			AdditionalText	OPTIONAL,
	additionalInformation	[10]	AdditionalInformation	OPTIONAL }

AttributeValueChangeInfo ::= SEQUENCE {
				sourceIndicator	SourceIndicator	OPTIONAL,
				attributeIdentifierList	[1] AttributeIdentifierList	OPTIONAL,
				attributeValueChangeDefinition	AttributeValueChangeDefinition,
				notificationIdentifier	NotificationIdentifier	OPTIONAL,
				correlatedNotifications  	[2] CorrelatedNotifications   OPTIONAL,
				additionalText			AdditionalText	OPTIONAL,
				additionalInformation    	[3]  AdditionalInformation  OPTIONAL}
ObjectInfo ::= SEQUENCE { sourceIndicator	SourceIndicator	OPTIONAL,
			attributeList	AttributeList	OPTIONAL,
			notificationIdentifier	NotificationIdentifier	OPTIONAL,
			correlatedNotifications  	[1] CorrelatedNotifications   OPTIONAL,
			additionalText			AdditionalText	OPTIONAL,
			additionalInformation    	[2]  AdditionalInformation  OPTIONAL}
RelationshipChangeInfo ::=  SEQUENCE {
				sourceIndicator	SourceIndicator	OPTIONAL,
				attributeIdentifierList	[1] AttributeIdentifierList	OPTIONAL,
				relationshipChangeDefinition	AttributeValueChangeDefinition,
				notificationIdentifier	NotificationIdentifier	OPTIONAL,
				correlatedNotifications  	[2] CorrelatedNotifications   OPTIONAL,
				additionalText			AdditionalText	OPTIONAL,
				additionalInformation    	[3]  AdditionalInformation  OPTIONAL}
StateChangeInfo ::= SEQUENCE {	sourceIndicator		SourceIndicator	OPTIONAL,
				attributeIdentifierList	[1] AttributeIdentifierList	OPTIONAL,
				stateChangeDefinition	AttributeValueChangeDefinition,
				notificationIdentifier	NotificationIdentifier	OPTIONAL,
				correlatedNotifications  	[2] CorrelatedNotifications   OPTIONAL,
				additionalText			AdditionalText	OPTIONAL,
				additionalInformation    	[3]  AdditionalInformation  OPTIONAL}
SecurityAlarmInfo  ::=  SEQUENCE {
	securityAlarmCause		SecurityAlarmCause,
	securityAlarmSeverity		SecurityAlarmSeverity,
	securityAlarmDetector  		SecurityAlarmDetector,
	serviceUser			ServiceUser,
	serviceProvider			ServiceProvider,
	notificationIdentifier		NotificationIdentifier	OPTIONAL,
	correlatedNotifications	[1]	CorrelatedNotifications  OPTIONAL,
	additionalText			AdditionalText	OPTIONAL,
	additionalInformation	[2]	AdditionalInformation	OPTIONAL}
END
