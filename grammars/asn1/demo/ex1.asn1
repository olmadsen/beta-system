%%% ex1: ModuleDefinition: asn1 %%%

ManagedObjectClassesDefinitions
	 {joint-iso-ccitt ms(9) smi(3) part2(2) asn1Module(2) 0}
DEFINITIONS ::=
BEGIN
smi2MObjectClass OBJECT IDENTIFIER
	 ::= {joint-iso-ccitt, ms(9), smi(3), part2(2), 1}
smi2NameBinding OBJECT IDENTIFIER
	 ::= {joint-iso-ccitt ms(9)  smi(3) part2(2) nameBinding(6) 2}
smi2Package   OBJECT IDENTIFIER
	 ::=  {joint-iso-ccitt ms(9)  smi(3) part2(2) package(4) 3}
END
